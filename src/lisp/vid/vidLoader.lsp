;;; ============================================================================
;;; LogicDWG Loader
;;; Release: 1.2.1 | Civil 3D 2026
;;; ============================================================================

(vl-load-com)

;; Preserve the actual loader path, including APPLOAD/drag-and-drop locations.
(setq LogicDWG:LoaderPath *load-truename*)

;; ============================================================
;; LogicDWG - Tool Files
;; Description: Tool files, loaded in alphabetical order.
;; ============================================================

(setq LogicDWG:Files
  '(
    "logicDwg.lsp"
    "vidBankCutting.lsp"
    "vidBlockLayer.lsp"
    "vidBoxText.lsp"
    "vidBridge.lsp"
    "vidCadMergeLayers.lsp"
    "vidCadOptimize.lsp"
    "vidChainageRunner.lsp"
    "vidCommanSettings.lsp"
    "vidDimMToFt.lsp"
    "vidDimSettings.lsp"
    "vidDgpsToBox.lsp"
    "vidDgpsToLine.lsp"
    "vidDgpsToOhe.lsp"
    "vidDgpsToSp.lsp"
    "vidGradient.lsp"
    "vidGradientAlign.lsp"
    "vidGradientCleanup.lsp"
    "vidIndexCurve.lsp"
    "vidIndexGradient.lsp"
    "vidLC.lsp"
    "vidLineToExportLevel.lsp"
    "vidLogicDwgGuide.lsp"
    "vidLogicDwgOnlineTools.lsp"
    "vidMapZone.lsp"
    "vidLayoutGen.lsp"
    "vidPublish.lsp"
    "vidRotText.lsp"
    "vidRwBoundaryMarker.lsp"
    "vidRwBoundaryText.lsp"
    "vidSurveySettings.lsp"
    "vidUnitSettings.lsp"
  )
)
;; ============================================================
;; Total Tool Files: 32
;; Sorting: Ascending alphabetical order (A-Z)
;; ============================================================



;; Find the tools folder. Works when this loader is on the Support File
;; Search Path, when it was loaded with APPLOAD / drag-and-drop from any
;; folder, or (last resort) by asking the user to pick logicDwg.lsp.
(defun LogicDWG:FindToolsDir (/ p dir loaderDir)
  (cond
    ((setq p (findfile "vid/tools/logicDwg.lsp"))
     (vl-filename-directory p))
    ((setq p (findfile "tools/logicDwg.lsp"))
     (vl-filename-directory p))
    ((setq p (findfile "logicDwg.lsp"))
     (vl-filename-directory p))
    (T
     (setq loaderDir
       (if LogicDWG:LoaderPath
         (vl-filename-directory LogicDWG:LoaderPath)
         nil
       )
     )
     (cond
       ((and loaderDir
             (setq dir (strcat loaderDir "\\tools"))
             (findfile (strcat dir "\\logicDwg.lsp")))
        dir)
       ((and (setq dir (strcat (getvar "DWGPREFIX") "tools"))
             (findfile (strcat dir "\\logicDwg.lsp")))
        dir)
       ((setq p (getfiled
                  "Locate LogicDWG tools folder (select logicDwg.lsp)"
                  "" "lsp" 4))
        (vl-filename-directory p))
       (T nil)
     )
    )
  )
)

;; Diagnostic / fallback: evaluate a file one top-level form at a time
;; (a top-level form starts with "(" in column 1) and report exactly which
;; form fails. Returns T when every form evaluated without error.
(defun LogicDWG:LoadByForm (full / f ln chunk chunks fail res)
  (setq f (open full "r"))
  (if (null f)
    nil
    (progn
      (while (setq ln (read-line f))
        (if (and (> (strlen ln) 0) (= (substr ln 1 1) "("))
          (progn
            (if chunk (setq chunks (cons chunk chunks)))
            (setq chunk ln)
          )
          (if chunk (setq chunk (strcat chunk "\n" ln)))
        )
      )
      (close f)
      (if chunk (setq chunks (cons chunk chunks)))
      (setq fail 0)
      (foreach c (reverse chunks)
        (setq res
          (vl-catch-all-apply
            '(lambda (x) (eval (read x)))
            (list c)
          )
        )
        (if (vl-catch-all-error-p res)
          (progn
            (setq fail (1+ fail))
            (princ (strcat "\n      FAILED FORM: "
                           (substr c 1 (min 70 (strlen c)))))
            (princ (strcat "\n      MESSAGE    : "
                           (vl-catch-all-error-message res)))
          )
        )
      )
      (= fail 0)
    )
  )
)

;; Load one file. An error in one file is reported but does not stop the rest.
;; If load fails, the file is retried form by form to show what is wrong.
(defun LogicDWG:LoadFile (folder filename / full res)
  (setq full (strcat folder "\\" filename))
  (cond
    ((not (findfile full))
     (princ (strcat "\n  [MISSING] " filename))
     nil
    )
    (T
     (setq res (vl-catch-all-apply 'load (list full)))
     (cond
       ((not (vl-catch-all-error-p res))
        (princ (strcat "\n  [OK]      " filename))
        T
       )
       (T
        (princ (strcat "\n  [ERROR]   " filename " : "
                       (vl-catch-all-error-message res)))
        (princ "\n    retrying form by form ...")
        (if (LogicDWG:LoadByForm full)
          (progn
            (princ (strcat "\n  [OK*]     " filename
                           " (loaded form by form)"))
            T
          )
          nil
        )
       )
     )
    )
  )
)


;; Locate and load the railway CUIX.
;; Searches beside the loader, beside the tools folder, and AutoCAD's support path.
(defun LogicDWG:FindCUIX (/ loader base toolsBase candidates p found)
  (setq loader LogicDWG:LoaderPath)
  (if (not loader)
    (setq loader (or (findfile "vidLoader.lsp") (findfile "vidLoader_fixed.lsp")))
  )
  (if loader
    (setq base (vl-filename-directory loader))
  )
  (if LogicDWG:ToolsDir
    (setq toolsBase (vl-filename-directory LogicDWG:ToolsDir))
  )
  (setq candidates
    (append
      (if base
        (list
          (strcat base "\\cui\\vid_railway.cuix")
          (strcat base "\\vid_railway.cuix")
          (strcat base "\\..\\cui\\vid_railway.cuix")
        )
        nil
      )
      (if toolsBase
        (list
          (strcat toolsBase "\\cui\\vid_railway.cuix")
          (strcat toolsBase "\\vid_railway.cuix")
        )
        nil
      )
      (list "vid_railway.cuix")
    )
  )
  (foreach candidate candidates
    (if (and (not found) (setq p (findfile candidate)))
      (setq found p)
    )
  )
  found
)

(defun LogicDWG:LoadCUI (/ cuiPath acad menuGroups result)
  (setq cuiPath (LogicDWG:FindCUIX))
  (cond
    ((null cuiPath)
     (princ "\n  [MISSING] vid_railway.cuix was not found.")
     (princ "\n  Expected: <vid folder>\\cui\\vid_railway.cuix")
     (princ "\n  Also searched the loader folder, tools parent, and AutoCAD support paths.")
     nil
    )
    (T
     (princ (strcat "\n  CUI file: " cuiPath))
     (setq result
       (vl-catch-all-apply
         '(lambda ()
            (setq acad (vlax-get-acad-object))
            (setq menuGroups (vla-get-MenuGroups acad))
            (vla-Load menuGroups cuiPath)
          )
         '()
       )
     )
     (if (vl-catch-all-error-p result)
       (progn
         (princ (strcat "\n  [ERROR] CUI load failed: "
                        (vl-catch-all-error-message result)))
         nil
       )
       (progn
         (princ "\n  [OK]      cui\\vid_railway.cuix loaded")
         T
       )
     )
    )
  )
)

(defun LogicDWG:LoadAll (/ loaded missing)
  (setq LogicDWG:ToolsDir (LogicDWG:FindToolsDir))
  (setq loaded 0 missing 0)

  (princ "\n============================================================")
  (princ "\n LogicDWG 1.2.1")
  (princ "\n============================================================")

  (LogicDWG:LoadCUI)

  (if (null LogicDWG:ToolsDir)
    (princ "\nTools folder not found. Put the 'tools' folder next to vidLoader.lsp.")
    (progn
      (princ (strcat "\nFolder: " LogicDWG:ToolsDir))
      (foreach f LogicDWG:Files
        (if (LogicDWG:LoadFile LogicDWG:ToolsDir f)
          (setq loaded (1+ loaded))
          (setq missing (1+ missing))
        )
      )
    )
  )

  (princ "\n------------------------------------------------------------")
  (princ (strcat "\nLoaded : " (itoa loaded) " / " (itoa (length LogicDWG:Files))))
  (princ (strcat "\nFailed : " (itoa (- (length LogicDWG:Files) loaded))))
  (if (= loaded (length LogicDWG:Files))
    (progn
      (princ "\n\nLogicDWG is ready. Type VIDLOGICDWG to open.")
      (princ "\nCommands: VIDCHAINAGERUNNER, VIDDGPSTOBOX, VIDLINETOEXPORTLEVEL, VIDDGPSTOLINE, VIDDGPSTOOHE, VIDDGPSTOSP, VIDDIMSETTINGS, VIDDIMMTOFT, VIDGRADIENT, VIDGRADIENTALIGN, VIDGRADIENTCLEANUP, VIDINDEXGRADIENT, VIDINDEXCURVE, VIDCADMERGELAYERS, VIDCADOPTIMIZE, VIDRWBOUNDARY, VIDBANKCUTTING, VIDBLOCKLAYER, VIDMAPZONE, VIDROTTEXT, VIDTR")
    )
    (princ "\n\nWARNING: LogicDWG did not load completely - see messages above.")
  )
  (princ "\n============================================================\n")
  (princ)
)

(LogicDWG:LoadAll)
(princ)
